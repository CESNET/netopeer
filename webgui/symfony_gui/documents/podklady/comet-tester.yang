module comet-tester {

  namespace "http://cesnet.cz/ns/yang/comet-tester";

  prefix "ct";

  import ietf-yang-types {
    prefix "yang";
  }

  import ietf-inet-types {
    prefix "inet";
  }

  /* Metadata */

  organization
    "CESNET, z. s. p. o.";

  contact
    "TBD";

  description
    "This YANG module defines the data model for the Combo Ethernet
     Tester.

     TBD - more information.
    ";

  revision 2012-05-09 {
    description
      "Initial revision.";
  }

  grouping enabled-switch {
    description
      "This grouping defines a switch which is used for
       enabling/disabling individual COMET modules.";
    leaf enabled {
      type boolean;
      default "true";
    }
  }

  grouping histogram64 {
    description
      "This grouping defines reusable contents for histograms with
       64-bit counters for each bin.

       Histograms are statistics, hence 'config false'.

       This grouping is supposed to be used in a container
       representing the entire histogram. Such a container node
       should provide, in its 'description' substatement, parameters
       necessary for interpreting the histogram counts, i. e. at
       least minimum and maximum values and the total number of bins.
      ";
    list bin {
      key "seq-number";
      config "false";
      max-elements "256";
      description
        "Each entry in this list gives the count of items in a single
         histogram bin identified by its sequence number.

         Maximum number of bins is 256.

         Sequence numbers of the entries must be increasing. However,
         entries for one or more bins may be missing - count of that
         bin is then considered to be zero.
        ";
      leaf seq-number {
        must "not(../preceding-sibling::bin/seq-number >=          "
           + ".)" {
          error-message
            "Histogram bins must be given in an increasing order.";
        }
        type uint8;
      }
      leaf count {
        description
          "Number of values in the corresponding histogram bin.";
        type uint64;
      }
    }
  }

  container comet-testers {
    list comet-tester {
      key "interface-id";
      leaf interface-id {
        type uint16 {
          range "0..max";
        }
      }
      container statistics {
        uses enabled-switch;
        container data {
          when "../enabled = 'true'";
          config "false";
          leaf pkt-sum {
            mandatory "true";
            must ". = ../pkt-rec + ../pkt-dis";
            description
              "Total packet count (received + discarded).";
            type yang:zero-based-counter64;
          }
          leaf pkt-rec {
            mandatory "true";
            description
              "Counter of received frames.";
            type yang:zero-based-counter64;
          }
          leaf pkt-dis {
            mandatory "true";
            description
              "Counter of discarded frames.";
            type yang:zero-based-counter64;
          }
          leaf pkt-bo {
            mandatory "true";
            description
              "Counter of packets causing buffer overflow.";
            type yang:zero-based-counter64;
          }
          leaf pkt-crc {
            mandatory "true";
            description
              "Counter of packets with CRC error.";
            type yang:zero-based-counter64;
          }
          leaf pkt-mac {
            mandatory "true";
            description
              "Counter of packets with bad MAC address.";
            type yang:zero-based-counter64;
          }
          leaf pkt-bmtu {
            mandatory "true";
            description
              "Counter of packets whose size is less than MTU.";
            type yang:zero-based-counter64;
          }
          leaf pkt-omtu {
            mandatory "true";
            description
              "Counter of packets whose size is greater than MTU.";
            type yang:zero-based-counter64;
          }
          leaf min-size {
            mandatory "true";
            must ". <= ../max-size";
            description
              "Minimum size.";
            type uint32;
          }
          leaf max-size {
            mandatory "true";
            description
              "Maximum size.";
            type uint32;
          }
          leaf min-delay {
            mandatory "true";
            must ". <= ../max-delay";
            description
              "XGMII minimum delay.";
            type uint64;
            units "bytes";
          }
          leaf max-delay {
            mandatory "true";
            description
              "XGMII maximum delay.";
            type uint64;
            units "bytes";
          }
          leaf avg-bitrate {
            mandatory "true";
            description
              "Average bitrate.";
            type uint64;
            units "Mbps";
          }
          leaf avg-pkt-size {
            mandatory "true";
            description
              "Average packet size.";
            type uint64;
            units "bytes";
          }
          container packet-sizes {
            description
              "Histogram of observed packet sizes.

               TBD - specify values of histogram parameters.
              ";
            uses histogram64;
          }
          container packet-gaps {
            description
              "Histogram of observed interpacket gaps.

               TBD - specify values of histogram parameters.
              ";
            uses histogram64;
          }
        }
      }
      container sender {
        uses enabled-switch;
        leaf timestamp {
          description
            "Timestamp of the first packet.";
          type uint64;
          units "nanoseconds";
        }
        leaf start-delay {
          description
            "Delay of the first packet.";
          type uint64;
          units "nanoseconds";
        }
        leaf interval {
          description
            "Time interval between packets.";
          type uint64;
          units "nanoseconds";
        }
        leaf copies {
          description
            "Number of copies of each packet.";
          type uint32;
        }
        leaf speed {
          description
            "Transmission speed.";
          type uint64;
          units "bits/s";
        }
        leaf hw-timestamp {
          description
            "If true, get the first timestamp from hardware.";
          type boolean;
        }
        container pcap-files {
          description
            "List of uploaded pcap files. At any moment, only one of
             them is active.";
          leaf active {
            description
              "Reference to the number of the active pcap file.

               No file is active if this leaf is missing.
              ";
            type leafref {
              path "../pcap-file/number";
            }
          }
          list pcap-file {
            description
              "URL of the PCAP file with a sequence number.

               Numbers must always form an increasing sequence.
              ";
            key "number";
            leaf number {
              type uint8 {
                range "1..max";
              }
              must "not(. <=                 "
                 + "../preceding-sibling::pcap-file/number)" {
                error-message
                  "Sequence numbers must be increasing.";
              }
            }
            leaf url {
              type inet:uri;
            }
          }
        }
        container data {
          when "../enabled = 'true'";
          config "false";
          leaf status {
            mandatory "true";
            description
              "Operational status of the sender module.";
            type enumeration {
              enum idle;
              enum sending;
              enum waiting;
            }
          }
        }
      }
      container output-packet-checker {
        uses enabled-switch;
      }
      container input-packet-checker {
        uses enabled-switch;
        container data {
          when "../enabled = 'true'";
          config "false";
          leaf inord {
            mandatory "true";
            description
              "Counter of packets arriving in order.";
            type yang:zero-based-counter64;
          }
          leaf outord {
            mandatory "true";
            description
              "Counter of packets arriving out of order.";
            type yang:zero-based-counter64;
          }
          leaf lost {
            mandatory "true";
            description
              "Counter of lost packets.";
            type yang:zero-based-counter64;
          }
          leaf error {
            mandatory "true";
            description
              "Counter of packets with errors.";
            type yang:zero-based-counter64;
          }
          leaf max-delay {
            mandatory "true";
            description
              "Maximum packet delay.";
            type uint64;
            units "nanoseconds";
          }
          leaf min-delay {
            mandatory "true";
            description
              "Minimum packet delay.";
            type uint64;
            units "nanoseconds";
          }
          leaf avg-delay {
            mandatory "true";
            description
              "Average packet delay.";
            type uint64;
          }
          container packet-delays {
            description
              "Histogram of observed packet delays.

               TBD - specify values of histogram parameters.
              ";
            uses histogram64;
          }
        }
      }
      container blackhole {
        uses enabled-switch;
      }
      container physical-coding-sublayer {
        uses enabled-switch;
        leaf sys-loopback-enabled {
          description
            "Enable system loopback.";
          type boolean;
        }
        leaf net-loopback-enabled {
          description
            "Enable network loopback.";
          type boolean;
        }
        leaf low-power-enabled {
          description
            "Enable low power.";
          type boolean;
        }
        leaf rx-scr-enabled {
          description
            "Enable RX descrambler.";
          type boolean;
        }
        leaf tx-scr-enabled {
          description
            "Enable TX scrambler.";
          type boolean;
        }
        container data {
          config "false";
          leaf tx-fault {
            mandatory "true";
            description
              "TX fault indicator.";
            type boolean;
          }
          leaf rx-fault {
            mandatory "true";
            description
              "RX fault indicator.";
            type boolean;
          }
          leaf high-ber {
            mandatory "true";
            description
              "High BER indicator";
            type boolean;
          }
          leaf ber-count {
            mandatory "true";
            description
              "BER counter.";
            type uint8;
          }
          leaf errblk-count {
            mandatory "true";
            description
              "Counter of blocks with errors.";
            type uint8;
          }
          leaf block-lock {
            mandatory "true";
            description
              "Block lock indicator.";
            type boolean;
          }
        }
      }
    }
  }

  /* RPCs */

  rpc reset-modules {
    description
      "Reset one or more COMET modules.";
    input {
      leaf-list submodule {
        description
          "Names of the modules.";
        type enumeration {
          enum input-packet-checker;
          enum output-packet-checker;
          enum sender;
        }
      }
    }
  }

  rpc reset-counters {
    description
      "Reset all counters in one or more COMET modules.";
    input {
      leaf-list submodule {
        description
          "Names of the modules.";
        type enumeration {
          enum statistics;
          enum input-packet-checker;
          enum output-packet-checker;
          enum physical-coding-sublayer;
        }
      }
    }
  }

  rpc send-traffic {
    description
      "Send traffic from active pcap file";
    input {
      leaf mode {
        description
          "Mode of sending";
        type enumeration {
          enum full-speed;
          enum user-speed;
          enum interval;
        }
      }
      leaf interface {
        description
          "Output interface.";
        type uint16;
      }
    }
  }
}
