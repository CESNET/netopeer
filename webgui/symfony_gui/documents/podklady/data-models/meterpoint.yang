module meterpoint {
  namespace "urn:cesnet:tmc:meterpoint:1.0";
  prefix meter;

  import ietf-yang-types {
    prefix yang;
  }

  organization "CESNET, z.s.p.o.";
  contact
    "rkrejci@cesnet.cz";
  description
    "Module specifying CESNET meterpoint configuration data model and RPC operations.";

  revision 2012-04-06 {
    description
      "Initial revision";
  }

  typedef decimal {
    type string {
      pattern "[0-9]+(\\.[0-9]+)?";
    }
    description
      "Simple decimal numbers type definition";
  }

  container meterpoint {
    container system {
      config false;
      leaf cpu_count {
        type uint8;
        description "Number of CPU cores.";
      }
      leaf memory_total {
        type uint32;
        description "Total size of the system memory.";
      }
      leaf cpu_usage {
        type string;
        description "TODO - jake statistiky a jak detailni?";
      }
    }
  }
}
