module "ietf-system-tls-auth" {
  yang-version "1";
  namespace "urn:ietf:params:xml:ns:yang:ietf-system-tls-auth";
  prefix "system-tls-auth";
  import "ietf-system" {
    prefix "sys";
  }

  import "ietf-netconf-acm" {
    prefix "nacm";
  }

  import "ietf-yang-types" {
    prefix "yang";
  }

  import "ietf-x509-cert-to-name" {
    prefix "x509c2n";
  }

  organization
    "IETF NETCONF (Network Configuration) Working Group";
  contact
    "WG Web:   <http://tools.ietf.org/wg/netconf/>
WG List:  <mailto:netconf@ietf.org>

WG Chair: Mehmet Ersue
       <mailto:mehmet.ersue@nsn.com>

WG Chair: Bert Wijnen
       <mailto:bertietf@bwijnen.net>

Editor:   Kent Watsen
       <mailto:kwatsen@juniper.net>

       Juergen Schoenwaelder
       <mailto:j.schoenwaelder@jacobs-university.de>";
  description
    "This module augments the ietf-system module in order to
add TLS authentication configuration nodes to the
'authentication' container.

Copyright (c) 2014 IETF Trust and the persons identified as
authors of the code. All rights reserved.

Redistribution and use in source and binary forms, with or
without modification, is permitted pursuant to, and subject
to the license terms contained in, the Simplified BSD
License set forth in Section 4.c of the IETF Trust's
Legal Provisions Relating to IETF Documents
(http://trustee.ietf.org/license-info).

This version of this YANG module is part of RFC XXXX; see
the RFC itself for full legal notices.";
  revision "2014-05-24" {
    description
      "Initial version";
    reference
      "RFC XXXX: NETCONF Server Configuration Model";
  }

  feature "tls-map-certificates" {
    description
      "The tls-map-certificates feature indicates that the
NETCONF server implements mapping X.509 certificates to NETCONF
usernames.";
  }

  feature "tls-map-pre-shared-keys" {
    description
      "The tls-map-pre-shared-keys feature indicates that the
NETCONF server implements mapping TLS pre-shared keys to NETCONF
usernames.";
  }

  grouping "tls-global-config" {
    container "trusted-ca-certs" {
      description
        "A list of Certificate Authority (CA) certificates that a
NETCONF server can use to authenticate a NETCONF client's
certificate.  A client's certificate is authenticated if
its Issuer matches one of the configured trusted CA
certificates.";
      leaf-list "trusted-ca-cert" {
        type "binary";
        description
          "The binary certificate structure, as
specified by RFC 5246, Section 7.4.6, i.e.,:

opaque ASN.1Cert<1..2^24>;

";
        reference
          "RFC 5246: The Transport Layer Security (TLS)
  Protocol Version 1.2";
      }

    }

    container "trusted-client-certs" {
      description
        "A list of client certificates that a NETCONF server can
use to authenticate a NETCONF client's certificate.  A
client's certificate is authenticated if it is an exact
match to one of the configured trusted client certificates.";
      leaf-list "trusted-client-cert" {
        type "binary";
        description
          "The binary certificate structure, as
specified by RFC 5246, Section 7.4.6, i.e.,:

opaque ASN.1Cert<1..2^24>;

";
        reference
          "RFC 5246: The Transport Layer Security (TLS)
  Protocol Version 1.2";
      }

    }

    container "cert-maps" {
      if-feature "tls-map-certificates";
      description
        "The cert-maps container is used by a NETCONF server to
map the NETCONF client's presented X.509 certificate to
a NETCONF username.

If no matching and valid cert-to-name list entry can be
found, then the NETCONF server MUST close the connection,
and MUST NOT accept NETCONF messages over it.";
      list "cert-to-name" {
        key "id";
        description
          "This list defines how certificates are mapped to names.
The name is derived by considering each cert-to-name
list entry in order. The cert-to-name entry's fingerprint
determines whether the list entry is a match:

1) If the cert-to-name list entry's fingerprint value
   matches that of the presented certificate, then consider
   the list entry as a successful match.

2) If the cert-to-name list entry's fingerprint value
   matches that of a locally held copy of a trusted CA
   certificate, and that CA certificate was part of the CA
   certificate chain to the presented certificate, then
   consider the list entry as a successful match.

Once a matching cert-to-name list entry has been found, the
map-type is used to determine how the name associated with
the certificate should be determined.  See the map-type
leaf's description for details on determining the name value.
If it is impossible to determine a name from the cert-to-name
list entry's data combined with the data presented in the
certificate, then additional cert-to-name list entries MUST
be searched looking for another potential match.

Security administrators are encouraged to make use of
certificates with subjectAltName fields that can be mapped to
names so that a single root CA certificate can allow all
child certificate's subjectAltName to map directly to a name
via a 1:1 transformation.";
        reference
          "SNMP-TLS-TM-MIB.snmpTlstmCertToTSNEntry";
        leaf "id" {
          type "uint32";
          description
            "The id specifies the order in which the entries in the
cert-to-name list are searched.  Entries with lower
numbers are searched first.";
          reference
            "SNMP-TLS-TM-MIB.snmpTlstmCertToTSNID";
        }

        leaf "fingerprint" {
          type "x509c2n:tls-fingerprint";
          mandatory "true";
          description
            "Specifies a value with which the fingerprint of the
certificate presented by the peer is compared.  If the
fingerprint of the certificate presented by the peer does
not match the fingerprint configured, then the entry is
skipped and the search for a match continues.";
          reference
            "SNMP-TLS-TM-MIB.snmpTlstmCertToTSNFingerprint";
        }

        leaf "map-type" {
          type "identityref" {
            base "cert-to-name";
          }

          mandatory "true";
          description
            "Specifies the algorithm used to map the certificate
presented by the peer to a name.

Mappings that need additional configuration objects should
use the 'when' statement to make them conditional based on
the 'map-type'.";
          reference
            "SNMP-TLS-TM-MIB.snmpTlstmCertToTSNMapType";
        }

        leaf "name" {
          when "../map-type = 'x509c2n:specified'";
          type "string";
          mandatory "true";
          description
            "Directly specifies the NETCONF username when the
'map-type' is 'specified'.";
          reference
            "SNMP-TLS-TM-MIB.snmpTlstmCertToTSNData";
        }

      }

    }

    container "psk-maps" {
      if-feature "tls-map-pre-shared-keys";
      description
        "During the TLS Handshake, the client indicates which
key to use by including a PSK identity in the TLS
ClientKeyExchange message. On the NETCONF server side,
this PSK identity is used to look up an entry in the psk-map
list. If such an entry is found, and the pre-shared keys
match, then the client is authenticated. The NETCONF
server uses the value from the user-name leaf in the
psk-map list as the NETCONF username.  If the NETCONF
server cannot find an entry in the psk-map list, or if
the pre-shared keys do not match, then the NETCONF
server terminates the connection.";
      reference
        "RFC 4279: Pre-Shared Key Ciphersuites for Transport Layer
  Security (TLS)";
      list "psk-map" {
        key "psk-identity";
        leaf "psk-identity" {
          type "string";
          description
            "The PSK identity encoded as a UTF-8 string. For
details how certain common PSK identity formats can
be encoded in UTF-8, see section 5.1. of RFC 4279.";
          reference
            "RFC 4279: Pre-Shared Key Ciphersuites for Transport
Layer Security (TLS)";
        }

        leaf "user-name" {
          type "nacm:user-name-type";
          mandatory "true";
          description
            "The NETCONF username associated with this PSK
identity.";
        }

        leaf "not-valid-before" {
          type "yang:date-and-time";
          description
            "This PSK identity is not valid before the given date
and time.";
        }

        leaf "not-valid-after" {
          type "yang:date-and-time";
          description
            "This PSK identity is not valid after the given date
and time.";
        }

        leaf "key" {
          nacm:default-deny-all;
          type "yang:hex-string";
          mandatory "true";
          description
            "The key associated with the PSK identity";
          reference
            "RFC 4279: Pre-Shared Key Ciphersuites for Transport
Layer Security (TLS)";
        }

      }

    }

  }

  augment "/sys:system/sys:authentication" {
    container "tls" {
      container "trusted-ca-certs" {
        description
          "A list of Certificate Authority (CA) certificates that a
NETCONF server can use to authenticate a NETCONF client's
certificate.  A client's certificate is authenticated if
its Issuer matches one of the configured trusted CA
certificates.";
        leaf-list "trusted-ca-cert" {
          type "binary";
          description
            "The binary certificate structure, as
specified by RFC 5246, Section 7.4.6, i.e.,:

opaque ASN.1Cert<1..2^24>;

";
          reference
            "RFC 5246: The Transport Layer Security (TLS)
  Protocol Version 1.2";
        }

      }

      container "trusted-client-certs" {
        description
          "A list of client certificates that a NETCONF server can
use to authenticate a NETCONF client's certificate.  A
client's certificate is authenticated if it is an exact
match to one of the configured trusted client certificates.";
        leaf-list "trusted-client-cert" {
          type "binary";
          description
            "The binary certificate structure, as
specified by RFC 5246, Section 7.4.6, i.e.,:

opaque ASN.1Cert<1..2^24>;

";
          reference
            "RFC 5246: The Transport Layer Security (TLS)
  Protocol Version 1.2";
        }

      }

      container "cert-maps" {
        if-feature "tls-map-certificates";
        description
          "The cert-maps container is used by a NETCONF server to
map the NETCONF client's presented X.509 certificate to
a NETCONF username.

If no matching and valid cert-to-name list entry can be
found, then the NETCONF server MUST close the connection,
and MUST NOT accept NETCONF messages over it.";
        list "cert-to-name" {
          key "id";
          description
            "This list defines how certificates are mapped to names.
The name is derived by considering each cert-to-name
list entry in order. The cert-to-name entry's fingerprint
determines whether the list entry is a match:

1) If the cert-to-name list entry's fingerprint value
   matches that of the presented certificate, then consider
   the list entry as a successful match.

2) If the cert-to-name list entry's fingerprint value
   matches that of a locally held copy of a trusted CA
   certificate, and that CA certificate was part of the CA
   certificate chain to the presented certificate, then
   consider the list entry as a successful match.

Once a matching cert-to-name list entry has been found, the
map-type is used to determine how the name associated with
the certificate should be determined.  See the map-type
leaf's description for details on determining the name value.
If it is impossible to determine a name from the cert-to-name
list entry's data combined with the data presented in the
certificate, then additional cert-to-name list entries MUST
be searched looking for another potential match.

Security administrators are encouraged to make use of
certificates with subjectAltName fields that can be mapped to
names so that a single root CA certificate can allow all
child certificate's subjectAltName to map directly to a name
via a 1:1 transformation.";
          reference
            "SNMP-TLS-TM-MIB.snmpTlstmCertToTSNEntry";
          leaf "id" {
            type "uint32";
            description
              "The id specifies the order in which the entries in the
cert-to-name list are searched.  Entries with lower
numbers are searched first.";
            reference
              "SNMP-TLS-TM-MIB.snmpTlstmCertToTSNID";
          }

          leaf "fingerprint" {
            type "x509c2n:tls-fingerprint";
            mandatory "true";
            description
              "Specifies a value with which the fingerprint of the
certificate presented by the peer is compared.  If the
fingerprint of the certificate presented by the peer does
not match the fingerprint configured, then the entry is
skipped and the search for a match continues.";
            reference
              "SNMP-TLS-TM-MIB.snmpTlstmCertToTSNFingerprint";
          }

          leaf "map-type" {
            type "identityref" {
              base "cert-to-name";
            }

            mandatory "true";
            description
              "Specifies the algorithm used to map the certificate
presented by the peer to a name.

Mappings that need additional configuration objects should
use the 'when' statement to make them conditional based on
the 'map-type'.";
            reference
              "SNMP-TLS-TM-MIB.snmpTlstmCertToTSNMapType";
          }

          leaf "name" {
            when "../map-type = 'x509c2n:specified'";
            type "string";
            mandatory "true";
            description
              "Directly specifies the NETCONF username when the
'map-type' is 'specified'.";
            reference
              "SNMP-TLS-TM-MIB.snmpTlstmCertToTSNData";
          }

        }

      }

      container "psk-maps" {
        if-feature "tls-map-pre-shared-keys";
        description
          "During the TLS Handshake, the client indicates which
key to use by including a PSK identity in the TLS
ClientKeyExchange message. On the NETCONF server side,
this PSK identity is used to look up an entry in the psk-map
list. If such an entry is found, and the pre-shared keys
match, then the client is authenticated. The NETCONF
server uses the value from the user-name leaf in the
psk-map list as the NETCONF username.  If the NETCONF
server cannot find an entry in the psk-map list, or if
the pre-shared keys do not match, then the NETCONF
server terminates the connection.";
        reference
          "RFC 4279: Pre-Shared Key Ciphersuites for Transport Layer
  Security (TLS)";
        list "psk-map" {
          key "psk-identity";
          leaf "psk-identity" {
            type "string";
            description
              "The PSK identity encoded as a UTF-8 string. For
details how certain common PSK identity formats can
be encoded in UTF-8, see section 5.1. of RFC 4279.";
            reference
              "RFC 4279: Pre-Shared Key Ciphersuites for Transport
Layer Security (TLS)";
          }

          leaf "user-name" {
            type "nacm:user-name-type";
            mandatory "true";
            description
              "The NETCONF username associated with this PSK
identity.";
          }

          leaf "not-valid-before" {
            type "yang:date-and-time";
            description
              "This PSK identity is not valid before the given date
and time.";
          }

          leaf "not-valid-after" {
            type "yang:date-and-time";
            description
              "This PSK identity is not valid after the given date
and time.";
          }

          leaf "key" {
            nacm:default-deny-all;
            type "yang:hex-string";
            mandatory "true";
            description
              "The key associated with the PSK identity";
            reference
              "RFC 4279: Pre-Shared Key Ciphersuites for Transport
Layer Security (TLS)";
          }

        }

      }

    }

  }

  grouping "x509c2n:cert-to-name" {
    list "cert-to-name" {
      key "id";
      description
        "This list defines how certificates are mapped to names.
The name is derived by considering each cert-to-name
list entry in order. The cert-to-name entry's fingerprint
determines whether the list entry is a match:

1) If the cert-to-name list entry's fingerprint value
   matches that of the presented certificate, then consider
   the list entry as a successful match.

2) If the cert-to-name list entry's fingerprint value
   matches that of a locally held copy of a trusted CA
   certificate, and that CA certificate was part of the CA
   certificate chain to the presented certificate, then
   consider the list entry as a successful match.

Once a matching cert-to-name list entry has been found, the
map-type is used to determine how the name associated with
the certificate should be determined.  See the map-type
leaf's description for details on determining the name value.
If it is impossible to determine a name from the cert-to-name
list entry's data combined with the data presented in the
certificate, then additional cert-to-name list entries MUST
be searched looking for another potential match.

Security administrators are encouraged to make use of
certificates with subjectAltName fields that can be mapped to
names so that a single root CA certificate can allow all
child certificate's subjectAltName to map directly to a name
via a 1:1 transformation.";
      reference
        "SNMP-TLS-TM-MIB.snmpTlstmCertToTSNEntry";
      leaf "id" {
        type "uint32";
        description
          "The id specifies the order in which the entries in the
cert-to-name list are searched.  Entries with lower
numbers are searched first.";
        reference
          "SNMP-TLS-TM-MIB.snmpTlstmCertToTSNID";
      }

      leaf "fingerprint" {
        type "x509c2n:tls-fingerprint";
        mandatory "true";
        description
          "Specifies a value with which the fingerprint of the
certificate presented by the peer is compared.  If the
fingerprint of the certificate presented by the peer does
not match the fingerprint configured, then the entry is
skipped and the search for a match continues.";
        reference
          "SNMP-TLS-TM-MIB.snmpTlstmCertToTSNFingerprint";
      }

      leaf "map-type" {
        type "identityref" {
          base "cert-to-name";
        }

        mandatory "true";
        description
          "Specifies the algorithm used to map the certificate
presented by the peer to a name.

Mappings that need additional configuration objects should
use the 'when' statement to make them conditional based on
the 'map-type'.";
        reference
          "SNMP-TLS-TM-MIB.snmpTlstmCertToTSNMapType";
      }

      leaf "name" {
        when "../map-type = 'x509c2n:specified'";
        type "string";
        mandatory "true";
        description
          "Directly specifies the NETCONF username when the
'map-type' is 'specified'.";
        reference
          "SNMP-TLS-TM-MIB.snmpTlstmCertToTSNData";
      }

    }

  }

}
