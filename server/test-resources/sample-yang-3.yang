module module1 {
	grouping group2 {
		leaf from_group2 {
			type string;
		}
	}
	container container1 {
		leaf-list leaflist {
			type int32;
		}
		container container2 {
			leaf leaf1 {
				type string;
			}
			list list1 {
				key "name";
				leaf name {
					type string;
				}
				leaf somevalue {
					type string;
				}
			}
		}
	}
}
